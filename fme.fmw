FME workspace fme.fmw
Startup Python:
      import smtplib
      from email.mime.text import MIMEText
      import fme
      from datetime import date
      from datetime import datetime

      subject = "Sentinel"
      today =  date.today()
      today = today.strftime("%d/%m/%Y")
      time = datetime.now()
      time = time.strftime("%H:%M")
      body = """Drogi użytkowniku {},
          o godzinie {} {} rozpoczęto przetwarzanie danych dla powiatu {}.""".format(fme.macroValues['emailKlient'], time, today, fme.macroValues['powiat'])
      sender = fme.macroValues['email']
      recipients = fme.macroValues['emailKlient']
      password = fme.macroValues['haslo']


      def send_email(subject, body, sender, recipients, password):
          msg = MIMEText(body)
          msg['Subject'] = subject
          msg['From'] = sender
          msg['To'] = ', '.join(recipients)
          with smtplib.SMTP_SSL('smtp.gmail.com', 465) as smtp_server:
             smtp_server.login(sender, password)
             smtp_server.sendmail(sender, recipients, msg.as_string())
          print("Message sent!")


      send_email(subject, body, sender, recipients, password)
Shutdown Python:
      import smtplib
      from email.mime.text import MIMEText
      import fme
      from datetime import date
      from datetime import datetime

      subject = "Sentinel"
      today =  date.today()
      today = today.strftime("%d/%m/%Y")
      time = datetime.now()
      time = time.strftime("%H:%M")
      body = """Drogi użytkowniku {},
          przetwarzanie danych dla powiatu {} zakończono sukcesem o godzinie {} {}.""".format(fme.macroValues['emailKlient'], fme.macroValues['powiat'], time, today)
      sender = fme.macroValues['email']
      recipients = fme.macroValues['emailKlient']
      password = fme.macroValues['haslo']


      def send_email(subject, body, sender, recipients, password):
          msg = MIMEText(body)
          msg['Subject'] = subject
          msg['From'] = sender
          msg['To'] = ', '.join(recipients)
          with smtplib.SMTP_SSL('smtp.gmail.com', 465) as smtp_server:
             smtp_server.login(sender, password)
             smtp_server.sendmail(sender, recipients, msg.as_string())
          print("Message sent!")


      send_email(subject, body, sender, recipients, password)

Parameters:
- email = izabela.kukurydza@gmail.com   # adres e-mail
- emailKlient = izabela.kukurydza@gmail.com   # Adres e-mail klienta
- powiat = łosicki   # Nazwa powiatu
- haslo =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   # Hasło
- chmury = 70   # Maksymalne pokrycie chmurami
- dataPoczatkowa = 20230701000000   # Data początkowa
- dataKoncowa = 20230730000000   # Data końcowa
- api = 8f734d39-bd34-43e9-8bfb-1431ed378c4e   # API Key
- SourceDataset_SHAPEFILE = $(FME_MF_DIR)powiaty\powiaty.shp   # Source Esri Shapefile(s)
- DestDataset_GEOTIFF = C:\Users\zuzka\Documents\studia\GEOINFA\Bazy_danych_przestrzennych\lab9   # Destination GeoTIFF Folder

Readers:
- SHAPEFILE_1: SHAPEFILE from $(SourceDataset_SHAPEFILE)

Writers:
- GEOTIFF_1: GEOTIFF to $(DestDataset_GEOTIFF)

powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> TestFilter
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(JPT_NAZWA_) CONTAINS $(powiat)",JPT_NAZWA_ = __powiat_
    JPT_NAZWA_ = __powiat_ -> Inspector_2
    JPT_NAZWA_ = __powiat_ -> Reprojector
Inspector_2
Reprojector
    DEST = EPSG:4326
    INTERPOLATION_TYPE_NAME = Nearest Neighbor
    RASTER_CELL_SIZE = Preserve Cells
    RASTER_TOLERANCE = 0.0
    REPROJECTED -> BoundingBoxAccumulator
    REPROJECTED -> Clipper [CLIPPER]
BoundingBoxAccumulator
    ACCUM_ATTRS_NAME = Use Attributes From One Feature
    BOUNDING_BOX -> EarthCacheConnector
EarthCacheConnector
    api_key = $(api)
    end_date = $(dataKoncowa)
    interval = 1
    min_aoi_coverage_percentage = $(chmury)
    output_id = rgbn-a3e8-11e7-9793-ae4260ee3b4b
    pipeline_name = sent8
    start_date = $(dataPoczatkowa)
    -> Inspector
    -> Sampler
    <Rejected> -> Terminator
Inspector
Sampler
    RATE = 1
    SAMPLE_MODE = No
    SAMPLE_TYPE_LONG = First N Features
    SAMPLED -> RasterBandSeparator
RasterBandSeparator
    BAND_INDEX_FIELD = _band_index
    PALETTE_INDEX_FIELD = _palette_index
    RASTER_INDEX_FIELD = _raster_index
    SPLIT_BY_NAME = Band and Palette
    -> TestFilter_2
    -> TestFilter_3
TestFilter_2
    DEFAULT_VALUE = <UNFILTERED>
    PASSED_TEST_GROUP_OUTPUT = FIRST
    TEST_LIST = "BOOL_OP,OR,COMPOSITE_TEST,""""""1"""""",TEST_CLAUSE,TEST @Value(_band_index) = 0",@Value(_band_index) = 0
    @Value(_band_index) = 0 -> NDVICalculator [Red]
TestFilter_3
    DEFAULT_VALUE = <UNFILTERED>
    PASSED_TEST_GROUP_OUTPUT = FIRST
    TEST_LIST = "BOOL_OP,OR,COMPOSITE_TEST,""""""1"""""",TEST_CLAUSE,TEST @Value(_band_index) = 3",@Value(_band_index) = 3
    @Value(_band_index) = 3 -> NDVICalculator [Infrared]
NDVICalculator
    COLORIZE = Blue-Yellow-Green Palette
    INDEXTYPE = NDVI
    SAVIADJUSTMENT = 0.5
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Inspector_3
    INSIDE -> ndvi (writer GEOTIFF_1)
    INSIDE -> RasterStatisticsCalculator
ndvi (writer GEOTIFF_1)
    attributes: gml_id char(254), JPT_SJR_KO char(254), JPT_POWIER char(254), JPT_KOD_JE char(254), JPT_NAZWA_ char(254), JPT_ORGAN_ char(254), JPT_JOR_ID char(254), WERSJA_OD char(254), WERSJA_DO char(254), WAZNY_OD char(254), WAZNY_DO char(254), JPT_KOD__1 char(254), JPT_NAZWA1 char(254), JPT_ORGAN1 char(254), JPT_WAZNA_ char(254), ID_BUFORA_ char(254), ID_BUFORA1 char(254), ID_TECHNIC char(254), IIP_PRZEST char(254), IIP_IDENTY char(254), IIP_WERSJA char(254), JPT_KJ_IIP char(254), JPT_KJ_I_1 char(254), JPT_KJ_I_2 char(254), JPT_OPIS char(254), JPT_SPS_KO char(254), ID_BUFOR_1 char(254), JPT_ID char(254), JPT_POWI_1 char(254), JPT_KJ_I_3 char(254),
      JPT_GEOMET char(254), JPT_GEOM_1 char(254), SHAPE_LENG char(254), SHAPE_AREA char(254), REGON char(254), RODZAJ char(254)
Inspector_3
RasterStatisticsCalculator
    RASTER_LEVEL = BAND_ONLY
    RASTER_STATS = "0   MEAN   STDEV   "
    -> Inspector_4
Inspector_4
Terminator
    MESSAGE = Translation Terminated
